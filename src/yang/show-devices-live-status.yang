module show-devices-live-status {

  namespace "http://example.com/show-devices-live-status";
  prefix show-devices-live-status;

  import ietf-inet-types {
    prefix inet;
  }
  import tailf-common {
    prefix tailf;
  }
  import tailf-ncs {
    prefix ncs;
  }

  description
    "Bla bla...";

  revision 2016-01-01 {
    description
      "Initial revision.";
  }

  container action {
    tailf:action show {
      tailf:actionpoint show-devices-live-status-action;
      input {
        leaf command {
          type string;
        }
      }
      output {
        leaf result {
          type string;
        }
      }
    }
  }
}
